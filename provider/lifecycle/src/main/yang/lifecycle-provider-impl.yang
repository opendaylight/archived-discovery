/*
 * Copyright (c) 2014 Ciena Corporation and others.  All rights reserved.
 *
 * This program and the accompanying materials are made available under the
 * terms of the Eclipse Public License v1.0 which accompanies this distribution,
 * and is available at http://www.eclipse.org/legal/epl-v10.html
 */
module lifecycle-provider-impl {

    yang-version 1;
    namespace "urn:opendaylight:params:xml:ns:yang:controller:config:lifecycle-provider:impl";
    prefix "lifecycle-provider-impl";

    import config { prefix config; revision-date 2013-04-05; }
    import opendaylight-md-sal-binding { prefix mdsal; revision-date 2013-10-28; }

    description
        "This module contains the base YANG definitions for the lifecycle-provider
        implementation";

    revision "2014-08-19" {
        description
                "Initial revision";
    }

    // This is the definition of the service implementation as a module identity.
    identity lifecycle-provider-impl {
        base config:module-type;

        // Specifies the prefix for generated java classes.
        config:java-name-prefix LifecycleProvider;
    }

    // Augments the 'configuration' choice node under modules/module.
    // We consume the three main services, RPCs, DataStore, and Notifications
    augment "/config:modules/config:module/config:configuration" {
        case lifecycle-provider-impl {
            when "/config:modules/config:module/config:type = 'lifecycle-provider-impl'";

            container rpc-registry {
                uses config:service-ref {
                    refine type {
                        mandatory true;
                        config:required-identity mdsal:binding-rpc-registry;
                    }
                }
            }

            container notification-service {
                uses config:service-ref {
                    refine type {
                        mandatory true;
                        config:required-identity mdsal:binding-notification-service;
                    }
                }
            }

            container data-broker {
                uses config:service-ref {
                    refine type {
                        mandatory false;
                        config:required-identity mdsal:binding-async-data-broker;
                    }
                }
            }
            leaf synchronization-thread-pool-size {
                type uint16;
                description "The number of threads allocated to execute network element synchronization.";
            }
        }
    }
}
