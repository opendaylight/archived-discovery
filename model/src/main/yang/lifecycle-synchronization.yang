/*
 * Copyright (c) 2014 Ciena Corporation and others.  All rights reserved.
 *
 * This program and the accompanying materials are made available under the
 * terms of the Eclipse Public License v1.0 which accompanies this distribution,
 * and is available at http://www.eclipse.org/legal/epl-v10.html
 */
module lifecycle-synchronization {
    namespace "urn:opendaylight:lifecycle:synchronization";
    prefix "synchronize";

    import lifecycle { prefix lifecycle; }
    import yang-ext { prefix ext; }

    organization "Opedaylight";
    contact "opendaylight-dev@opendaylight.org";
    description
        "Provides RPCs and notifications required to support discovery,
        synchronization, and reconciliation of the network model. This
        module defines the RPCs and notifications used when synchronizing
        a newtork elements into the controller information model.";

    revision "2014-07-14" {
        description "Initial revision";
    }

    /*
     * Used to notify listeners that a network element has been synchronized
     * in that its configuration information has been pulled from the device
     * and reconsilved back into the controllers information model.
     */
    notification network-element-synchronized {
        uses lifecycle:lifecycle-header;
        leaf node-id {
            type string;
            mandatory false;
        }
        uses lifecycle:network-element-details;

        leaf changes {
            type boolean;
            mandatory true;
            description "Indicates if the synchronization of the network element introduced
                        changes into the controller information model";
        }
    }

    /*
     * Used to notify listeners that an attempt to synchronize a network element
     * has failed and provide the listener with the cause of the failure.
     */
    notification network-element-synchronization-failure {
        uses lifecycle:lifecycle-header;
        leaf node-id {
            type string;
            mandatory false;
        }
        uses lifecycle:network-element-details;

        leaf cause {
            type string;
            mandatory true;
        }
    }

    /*
     * Routed RPC implemented to support network element synchronization. This
     * should be implemented by node type support plugins to query data from
     * a network element and reconcile it into the controller's information
     * model.
     */
    rpc synchronize-network-element {
        description "Network element IP, Type, username, password";
        input {
            uses lifecycle:lifecycle-header;
            leaf network-element-type-ref {
                type instance-identifier;
                ext:context-reference lifecycle:network-element-type-context;
                mandatory true;
            }
            uses lifecycle:network-element-details;
        }
        output {
            uses lifecycle:lifecycle-header;
            choice result {
                default failure;
                case success {
                    leaf changes {
                        type boolean;
                        mandatory true;
                        description "Indicates if the synchronization of the network element introduced
                                                changes into the controller information model";
                    }
                }
                case failure {
                    leaf cause {
                        type string;
                        mandatory "true";
                    }
                }
                case pending {
                }
            }
        }
    }
}
