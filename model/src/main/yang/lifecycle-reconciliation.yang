/*
 * Copyright (c) 2014 Ciena Corporation and others.  All rights reserved.
 *
 * This program and the accompanying materials are made available under the
 * terms of the Eclipse Public License v1.0 which accompanies this distribution,
 * and is available at http://www.eclipse.org/legal/epl-v10.html
 */
module lifecycle-reconciliation {
    namespace "urn:opendaylight:lifecycle:reconciliation";
    prefix "reconciliation";

    import lifecycle { prefix lifecycle; }

    organization "Opedaylight";
    contact "opendaylight-dev@opendaylight.org";
    description
        "Provides RPCs and notifications required to support discovery,
        synchronization, and reconciliation of the network model. This
        module provides the notification sent when a new connection is
        resolved based on updated network information.";

    revision "2014-07-14" {
        description "Initial revision";
    }

    /*
     * Used to notify listeners that a nework element connection has been
     * resolved and added to the topology model of the controller.
     */
    notification network-connection-reconciled {
        uses lifecycle:lifecycle-header;
        leaf end-point-A {
            type string;
            mandatory true;
        }

        leaf end-point-B {
            type string;
            mandatory true;
        }
    }
}
