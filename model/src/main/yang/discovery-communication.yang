/*
 * Copyright (c) 2014 Ciena Corporation and others.  All rights reserved.
 *
 * This program and the accompanying materials are made available under the
 * terms of the Eclipse Public License v1.0 which accompanies this distribution,
 * and is available at http://www.eclipse.org/legal/epl-v10.html
 */
module discovery-communication {
    namespace "urn:opendaylight:discovery:communication";
    prefix "communication";

    import discovery { prefix discovery; }

    organization "Opedaylight";
    contact "opendaylight-dev@opendaylight.org";
    description
        "Provides RPCs and notifications required to support discovery, synchronization, communication, and reconciliation of the
        network model. This module defines the RPCs and notifications used when synchronizing a newtork elements into the controller
        information model.";

    revision "2014-10-20" {
        description "Initial revision";
    }

    /*
	 * Used to notify listeners that the communication between the network 
	 * element and the controller is down.
	 */
    notification network-element-communication-down {
        uses discovery:discovery-header;
        leaf node-id {
            type string;
            mandatory false;
        }
        uses discovery:network-element-details;

        leaf reason {
            type string;
            mandatory false;
            description "Indicates the reason for the ne communication loss";
        }
    }

    /*
     * Used to notify listeners that the communication between the network 
	 * element and the controller has been restored.	 
	 */
    notification network-element-communication-restored {
        uses discovery:discovery-header;
        leaf node-id {
            type string;
            mandatory false;
        }
        uses discovery:network-element-details;
    }
}
