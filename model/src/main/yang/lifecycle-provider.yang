/*
 * Copyright (c) 2014 Ciena Corporation and others.  All rights reserved.
 *
 * This program and the accompanying materials are made available under the
 * terms of the Eclipse Public License v1.0 which accompanies this distribution,
 * and is available at http://www.eclipse.org/legal/epl-v10.html
 */
module lifecycle-identification-provider {
    namespace "urn:opendaylight:lifecycle:identification:provider";
    prefix "lifecycle-identification-provider";

    import yang-ext { prefix ext; }
    import lifecycle { prefix lifecycle; }

    organization "Opedaylight";
    contact "opendaylight-dev@opendaylight.org";
    description
        "Provides RPCs and notifications required by the module to support
        identification of network elements as part of the lifecycle module";

    revision "2014-07-14" {
        description "Initial revision";
    }

    /*
     * Used to inform network element support plugins that a new network
     * element requires identification or binding to a node type. This should
     * trigger the plugins to attempt to connect to the network element and
     * validate if it is a supported type.
     */
    notification identify-network-element {
        uses lifecycle:lifecycle-header;
        uses lifecycle:network-element-details;
    }
}
