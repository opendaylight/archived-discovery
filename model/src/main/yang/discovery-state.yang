/*
 * Copyright (c) 2014 Ciena Corporation and others.  All rights reserved.
 *
 * This program and the accompanying materials are made available under the
 * terms of the Eclipse Public License v1.0 which accompanies this distribution,
 * and is available at http://www.eclipse.org/legal/epl-v10.html
 */
module discovery-state {
    namespace "urn:opendaylight:discovery:state";
    prefix "state";

    import discovery { prefix discovery; }

    organization "Opendaylight";
    contact "opendaylight-dev@opendaylight.org";
    description
        "Provides RPCs and notifications required to support discovery, synchronization, and reconciliation of the network model.
        This module defines the notifications used in the process to identify the node type associated to a network element.";

    revision "2014-07-14" {
        description "Initial revision";
    }

    /*
     * Used to inform listeners that a new network element has been
     * associated with a node type and added to inventory. At the point that
     * this notification is sent the network element has not been synchronized,
     * i.e. its configucation has not been loaded, it has simply been
     * assigned a node type.
     */
    notification discovery-state-change {
        uses discovery:discovery-header;
        uses discovery:node-id-header;
        uses discovery:network-element-details;
        leaf from-state {
            type discovery:state;
        }
        leaf to-state {
            type discovery:state;
        }
        leaf timestamp {
            type uint64;
        }
        leaf cause {
            type string;
        }
    }
    /*
      *This is to populate node-id-to-state table, it will only track device states, NOT request states
      */
    notification node-state-change {
        uses discovery:node-id-header;
        leaf state {
            type discovery:state;
        }
    }
}
