/*
 * Copyright (c) 2014 Ciena Corporation and others.  All rights reserved.
 *
 * This program and the accompanying materials are made available under the
 * terms of the Eclipse Public License v1.0 which accompanies this distribution,
 * and is available at http://www.eclipse.org/legal/epl-v10.html
 */
module lifecycle-state {
    namespace "urn:opendaylight:lifecycle:state";
    prefix "state";

    import lifecycle { prefix lifecycle; }

    organization "Opendaylight";
    contact "opendaylight-dev@opendaylight.org";
    description
        "Provides RPCs and notifications required to support discovery,
        synchronization, and reconciliation of the network model. This
        module defines the notifications used in the process to identify
        the node type associated to a network element.";

    revision "2014-07-14" {
        description "Initial revision";
    }

    /*
     * Used to inform listeners that a new network element has been
     * associated with a node type and added to inventory. At the point that
     * this notification is sent the network element has not been synchronized,
     * i.e. its configucation has not been loaded, it has simply been
     * assigned a node type.
     */
    notification lifecycle-state-change {
        uses lifecycle:lifecycle-header;
        uses lifecycle:network-element-details;
        leaf from-state {
            type lifecycle:state;
        }
        leaf to-state {
            type lifecycle:state;
        }
        leaf timestamp {
            type uint64;
        }
    }
}
