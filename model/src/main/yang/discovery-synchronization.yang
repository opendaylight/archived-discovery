/*
 * Copyright (c) 2014 Ciena Corporation and others.  All rights reserved.
 *
 * This program and the accompanying materials are made available under the
 * terms of the Eclipse Public License v1.0 which accompanies this distribution,
 * and is available at http://www.eclipse.org/legal/epl-v10.html
 */
module discovery-synchronization {
    namespace "urn:opendaylight:discovery:synchronization";
    prefix "synchronize";

    import discovery { prefix discovery; }
    import yang-ext { prefix ext; }

    organization "Opedaylight";
    contact "opendaylight-dev@opendaylight.org";
    description
        "Provides RPCs and notifications required to support discovery, synchronization, and reconciliation of the network model.
        This module defines the RPCs and notifications used when synchronizing a newtork elements into the controller information
        model.";

    revision "2014-07-14" {
        description "Initial revision";
    }

    /*
     * Used to notify listeners that a network element has been synchronized
     * in that its configuration information has been pulled from the device
     * and reconsilved back into the controllers information model.
     */
    notification network-element-synchronized {
        uses discovery:discovery-header;
        uses discovery:node-id-header;
        uses discovery:network-element-details;

        leaf changes {
            type boolean;
            mandatory true;
            description "Indicates if the synchronization of the network element introduced changes into the controller information model";
        }
    }

    /*
     * Used to notify listeners that an attempt to synchronize a network element
     * has failed and provide the listener with the cause of the failure.
     */
    notification network-element-synchronization-failure {
        uses discovery:discovery-header;
        uses discovery:node-id-header;
        uses discovery:network-element-details;

        leaf cause {
            type string;
            mandatory true;
        }
    }

    /*
     * Routed RPC implemented to support network element synchronization. This
     * should be implemented by node type support plugins to query data from
     * a network element and reconcile it into the controller's information
     * model.
     */
    rpc synchronize-network-element {
        description "Network element IP, Type, username, password";
        input {
            uses discovery:discovery-header;
            leaf network-element-type-ref {
                type instance-identifier;
                ext:context-reference discovery:network-element-type-context;
                mandatory true;
            }
            uses discovery:node-id-header;
            uses discovery:network-element-details;
        }
        output {
            uses discovery:discovery-header;
            uses discovery:node-id-header;
            choice result {
                default failure;
                case success {
                    leaf changes {
                        type boolean;
                        mandatory true;
                        description "Indicates if the synchronization of the network element introduced changes into the controller information model";
                    }
                }
                case failure {
                    leaf cause {
                        type string;
                        mandatory "true";
                    }
                }
                case pending {
                }
            }
        }
    }
}
